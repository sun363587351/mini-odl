module hello {
    yang-version 1.1;
    namespace "urn:opendaylight:params:xml:ns:yang:hello";
    prefix "hello";

    revision "2018-05-17" { // TODO change revision to date of model creation
        description "Initial revision of hello model";
    }
}
